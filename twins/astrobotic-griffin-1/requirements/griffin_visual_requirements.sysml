package GriffinVisualRequirements {
    private import Griffin1Requirements::Griffin1Lander;
    private import Griffin1Requirements::HostedRoverInterface;
    private import FlipRequirements::FlipRover;

    // Domain-owned requirement definitions. Griffin1Requirements owns only
    // the integrated system subject, requirement usages, and verification.

    requirement def GR015_NozzleGeometry {
        doc /* GR-015 [visual+physics] each named lander part resolves to geometry and the nozzle owns visible bell geometry that is not a collider. Rationale: visible propulsion detail must remain replaceable presentation while thrust/collision stay with the flight model. */
    }

    requirement def GR016_SolarLayout {
        doc /* GR-016 [mission configuration] realize the array count and Sun-quadrant arrangement defined by GriffinSolarRequirements::GSA001_ArrayCount and GSA003_SunQuadrantLayout, with every panel supported from the bus structure. */
    }

    requirement def GR020_ProxySuppression {
        doc /* GR-020 [visual ownership] suppress inherited comparison geometry when a named part owns the visible representation; hidden duplicates do not count as removal. Source: Twin component ownership policy. Rationale: inactive or hidden duplicates still obscure which component owns the rendered geometry and can reappear during composition. The obsolete solid PayloadAdapter/AdapterRing cylinder shall be removed; the maintained visible platform is Bus/RoverPayloadDeck, and the AdapterPlate physical interface is retained. Rationale: the render-only comparison disc obscured tank domes and presented an unsupported circular platform shape. */
    }

    requirement def GR032_MainEngineBells {
        doc /* GR-032 [public product value] model exactly seven visible, non-colliding main-engine bell geometries. Rationale: the public seven-engine architecture fixes the count; bell dimensions remain a separately labeled visual proxy. */
    }

    requirement def GR033_PropellantTanks {
        doc /* GR-033 [public integration value] model four visible, source-owned COPV study assemblies at the ordered GriffinVisualConfiguration tank stations and scales. The vessel skin and retention bands are render-only; flight propellant mass remains in MainPropulsion. The MliTank vessel skins shall bind to the vehicle MliFoil_Mat material. Its colour, crinkle density and sheen are appearance estimates inherited from lunco://shaders/mli_foil.wesl, not measured material optical properties. The gold blanket appearance is informed by https://www.esa.int/ESA_Multimedia/Images/2022/09/Griffin_lander and https://www.astrobotic.com/lunar-delivery/landers/griffin-lander/ (concept imagery, not a current flight CAD guarantee). Exact COPV dimensions and placement remain TBD. Rationale: four repeated tank owners represent the visible system without retaining incompatible Capsule placeholders; public material does not provide a certified tank ICD. */
    }

    requirement def GRV001_PresentationFrame {
        doc /* GV-001 [visual] the review composition shall expose an authored VisualCamera in the project SI/Y-up frame. Source: LunCoSim visual review contract. Rationale: a named camera makes visual evidence repeatable across headful and capture runs. Editor component previews must retain the canonical metric/Y-up stage frame and remain isolated from site-anchor placement and simulation-domain authority. A georeferenced mission camera uses its actual site frame; these are distinct presentation contexts. Rationale: the integrated Griffin-FLIP Editor preview was rotated and displaced to lunar-radius coordinates while the same local vehicle preview was correct. Owner evidence: LunCoSim UsdPreviewOnly ancestry contract in crates/lunco-usd-bevy-scene/src/lib.rs; observed missing guard in crates/lunco-usd-sim-celestial/src/lib.rs. */
    }

    requirement def GRV002_LanderPresentation {
        doc /* GV-002 [visual] the review shall show Griffin-1 as a recognizable faceted lander with its four legs, payload deck, bus-edge high-gain antenna, a flat medium-gain panel on a seated standoff, and seven-engine cluster. Tank blankets shall use the shared object-space foil material with source-owned artistic appearance controls, referenced in GriffinVisualConfiguration; their visual pattern is not a validated thermal blanket specification. The medium-gain shape is inferred from PUG pages 20/30; its size, rear-face station and fixed review pose are explicit study assumptions, with dimensions and rationale in GriffinVisualConfiguration. Antenna topology follows Astrobotic Payload User Guide August 2021 v5.02 page 30; study mast, scale and parked tilt derive from GriffinVisualConfiguration. Source: https://www.astrobotic.com/wp-content/uploads/2022/01/PUGLanders_011222.pdf. The current visual study uses an octagonal open frame and a separate octagonal tank-support perimeter with four study tank openings; this is not a published tank ICD. */
    }

    requirement def GRV003_GriffinSolarAssemblies {
        doc /* GV-003 [visual] the review shall show the solar configuration defined by GriffinSolarRequirements::GSA001_ArrayCount and GSA003_SunQuadrantLayout as upright frame/cell assemblies on the forward face and both forward chamfers, each with a visible structural support path and the source-owned panel outline and clearances. Exact flight installation dimensions remain unpublished; this study layout preserves both rover egress corridors. */
    }

    requirement def GRV004_ScaleDatums {
        doc /* GV-004 [visual] review geometry shall agree with the SysML deck, wheel, landing-pad, and ground scale datums in metres. Source: Moon Base SI/Y-up project contract. Rationale: common scale datums are required to judge rover-to-lander proportions and contact plausibility. */
    }

    requirement def GRV005_RenderOwnership {
        doc /* GV-005 [visual ownership] presentation geometry shall be render-only where it is not a load-bearing collider; metric landing-pad datums are guide-only and hidden, and the test shall query collision, purpose, and visibility attributes. Source: LunCoSim visual/physics ownership policy. Rationale: visible study geometry must not quietly alter contact or mass behavior. */
    }

    requirement def GRV006_LunarContext {
        doc /* GV-006 [visual] the live mission shall retain the South-Pole terrain asset and canonical terrain_layered.wesl shader; static shape review shall use a visible render-only flat datum and one project light with child dynamics and mechanical joints disabled. Source: crates/lunco-usd-avian-reader/src/joint.rs uses physics:jointEnabled=false to suppress admission; enabled joints between static bodies leave pending admission. This is a static review override, not a change to the mission mechanism. The flat datum is a square, ENU-centered UsdGeomPlane explicitly carrying LunCoTerrainAPI and lunco:terrain:surfaceRole=flat-site. Its 36 m width/length is an estimated review footprint covering the lander and unfolded ramps, not lunar site data. The static inspection uses one directional Sun and a neutral untextured DomeLight fill with inputs:intensity=300 and inputs:exposure=0. These are renderer brightness settings, not measured lunar illuminance. Source: crates/lunco-usd-bevy-light/src/light.rs maps the dome intensity times 2^exposure to ambient brightness. Estimate rationale: owned 2026-10-03 A/B frames showed the former 18000 intensity at exposure 2 flattening frame depth and metallic highlights; 300 at exposure 0 preserves rail shadows while exposing the lit body and leg structure. This inspection fill does not alter mission lighting. Source: LunCoSim docs/architecture/60-curvature-elevation-and-gravity.md flat-site contract and crates/lunco-terrain-surface/src/georef.rs. The production mission retains its DEM owner. Source: owned foot-collider query and screenshot 2026-10-01. Rationale: a frozen parent above a varying DEM allowed dynamic legs to sag into the terrain; a flat unloaded review isolates proportions, while mission contact remains physical. */
    }

    requirement def GRV007_VisualEvidence {
        doc /* GV-007 [evidence] the visual verdict shall be emitted by Twin Rhai and paired with a captured frame and composed USD query from the same source revision. Source: Twin visual evidence gate. Rationale: matching source revision, query, and frame prevents stale screenshots from being presented as current model evidence. */
    }


    // System integration requirement usages owned by this domain.
    requirement <'GR-015'> gr015 : GR015_NozzleGeometry { subject lander : Griffin1Lander; }
    requirement <'GR-016'> gr016 : GR016_SolarLayout { subject lander : Griffin1Lander; }
    requirement <'GR-020'> gr020 : GR020_ProxySuppression { subject lander : Griffin1Lander; }
    requirement <'GR-032'> gr032 : GR032_MainEngineBells { subject lander : Griffin1Lander; }
    requirement <'GR-033'> gr033 : GR033_PropellantTanks { subject lander : Griffin1Lander; }
    requirement <'GV-001'> gv001 : GRV001_PresentationFrame { subject lander : Griffin1Lander; }
    requirement <'GV-002'> gv002 : GRV002_LanderPresentation { subject lander : Griffin1Lander; }
    requirement <'GV-003'> gv003 : GRV003_GriffinSolarAssemblies { subject lander : Griffin1Lander; }
    requirement <'GV-004'> gv004 : GRV004_ScaleDatums { subject lander : Griffin1Lander; subject rover : HostedRoverInterface; }
    requirement <'GV-005'> gv005 : GRV005_RenderOwnership { subject lander : Griffin1Lander; subject rover : HostedRoverInterface; }
    requirement <'GV-006'> gv006 : GRV006_LunarContext { subject lander : Griffin1Lander; }
    requirement <'GV-007'> gv007 : GRV007_VisualEvidence { subject lander : Griffin1Lander; subject rover : HostedRoverInterface; }



    verification def Verify_GriffinVisualRequirements {
        subject lander : Griffin1Lander;
        subject rover : HostedRoverInterface;
        subject flip : FlipRover;
        objective {
            verify GriffinVisualRequirements::gv001;
            verify GriffinVisualRequirements::gv002;
            verify GriffinVisualRequirements::gv003;
            verify GriffinVisualRequirements::gv004;
            verify GriffinVisualRequirements::gv005;
            verify GriffinVisualRequirements::gv006;
            verify GriffinVisualRequirements::gv007;
            verify FlipRequirements::fvg001;
        }
    }

}
